-- extracted from draft-bakke-iscsimib-01.txt
-- at Wed Aug  9 07:08:23 2000

ISCSI-MIB DEFINITIONS  ::= BEGIN

IMPORTS

   MODULE-IDENTITY, OBJECT-TYPE, Unsigned32,
   IpAddress, Counter32, Counter64,
   experimental
-- mib-2
       FROM SNMPv2-SMI
   DisplayString
--   DisplayString, RowStatus
       FROM SNMPv2-TC
   InterfaceIndex
       FROM IF-MIB
   MODULE-COMPLIANCE, OBJECT-GROUP
--   MODULE-COMPLIANCE, OBJECT-GROUP, NOTIFICATION-GROUP
       FROM SNMPv2-CONF
   ;

iscsiModule MODULE-IDENTITY
        LAST-UPDATED                "0007280000Z" -- July 28, 2000
        ORGANIZATION                "NuSpeed, Inc"
        CONTACT-INFO
                "
                Mark Bakke
                Postal: NuSpeed, Inc
                        6450 Wedgwood Road
                        Maple Grove, MN
                        USA 55311

                Tel: +1 763-398-1000
                Fax: +1 763-398-1001

                E-mail: mark.bakke@nuspeed.com

                Jim Muchow
                Postal: NuSpeed, Inc
                        6450 Wedgwood Road
                        Maple Grove, MN
                        USA 55311

                Tel: +1 763-398-1000
                Fax: +1 763-398-1001

                E-mail: jim.muchow@nuspeed.com"
        DESCRIPTION
                "."

     REVISION "0007280000Z"   -- July 28, 2000
     DESCRIPTION "Update to re-arrange the tables so that
         the initiator table is now an expansion table
         for the base iSCSI table.
         Added a couple of additional variables, the
         targetLunNumber in the target table and the
         lunSerialNumber in the lun table.
         Also a better definition of the OBJECT-GROUPs. "

::= { experimental 1 }

iscsiMgmt OBJECT IDENTIFIER ::= { iscsiModule 1 }

iscsiObjects OBJECT IDENTIFIER ::= { iscsiMgmt 1 }
iscsiNotifications OBJECT IDENTIFIER ::= { iscsiMgmt 2 }
iscsiConformance OBJECT IDENTIFIER ::= { iscsiMgmt 3 }

-- Textual Conventions

-- IScsiLunId ::= OCTET STRING (SIZE(8))

IScsiConnectState ::= INTEGER {
        unknown       (1),
        notLoggedIn   (2),
        fullPhase     (3),
        loginDenied   (4),
        terminating   (5)
      }

IScsiAuthType ::= INTEGER {
        unknown       (1),
        none          (2),
        digest        (3)
        -- Work to do here.  Should this be a string, instead of an enum,
        -- for better flexibility?
      }

IScsiCheckType ::= INTEGER {
        unknown       (1),
        none          (2),  -- No extra checksums
        checksum16    (3),  -- 1s complement
        crc32         (4),  -- 32-bit CRC
        md5           (5)   -- MD5 hash
      }

  -- We need to get an experimental number for this MIB.

iscsiNumber  OBJECT-TYPE
        SYNTAX                       Unsigned32
        MAX-ACCESS                   read-only
        STATUS                       current
        DESCRIPTION
            "The number of iSCSI instances present on the system."
::= { iscsiObjects 1 }

iscsiTable OBJECT-TYPE
        SYNTAX                       SEQUENCE OF IscsiEntry
        MAX-ACCESS                   not-accessible
        STATUS                       current
        DESCRIPTION
            "."
::= { iscsiObjects 2 }

iscsiEntry OBJECT-TYPE
        SYNTAX                       IscsiEntry
        MAX-ACCESS                   not-accessible
        STATUS                       current
        DESCRIPTION
            "."
        INDEX                        { iscsiIndex }
::= { iscsiTable 1 }

IscsiEntry ::= SEQUENCE {
        iscsiIndex                   Unsigned32,
        iscsiName                    DisplayString,
        iscsiDescription             DisplayString,
        rxMsgs                       Counter32,
        rxPingCmdMsgs                Counter32,
        rxScsiCmdMsgs                Counter32,
        rxScsiCmdMsgsRejected        Counter32,
        rxTaskMgtMsgs                Counter32,
        rxTaskMgtMsgsRejected        Counter32,
        rxLoginCmdMsgs               Counter32,
        rxLoginCmdMsgsRejected       Counter32,
        rxTextCmdMsgs                Counter32,
        rxTextCmdMsgsRejected        Counter32,
        rxInvalidMsgs                Counter32,
        rxDataMsgs                   Counter32,
        rxDataBytes                  Counter64,
        rxDataMsgsDiscarded          Counter32,
        rxDataBytesDiscarded         Counter32,
        txMsgs                       Counter32,
        txPingRspMsgs                Counter32,
        txScsiRspMsgs                Counter32,
        txScsiTaskMgtRspMsgs         Counter32,
        txLoginRspMsgs               Counter32,
        txTextRspMsgs                Counter32,
        txRttMsgs                    Counter32,
        txAsyncEvtMsgs               Counter32,
        txInvalidOpcodeMsgs          Counter32,
        txDataMsgs                   Counter32,
        txDataBytes                  Counter64,
        connectionsCreated           Counter32,
        connectionsRefused           Counter32,
        connectionsTerminated        Counter32,
        connectionsErrored           Counter32
}

iscsiIndex OBJECT-TYPE
     SYNTAX Unsigned32
     MAX-ACCESS read-only
     STATUS current
     DESCRIPTION "."
::= { iscsiEntry 1 }
iscsiName OBJECT-TYPE
     SYNTAX DisplayString
     MAX-ACCESS read-only
     STATUS current
     DESCRIPTION "."
::= { iscsiEntry 2 }
iscsiDescription OBJECT-TYPE
     SYNTAX DisplayString
     MAX-ACCESS read-only
     STATUS current
     DESCRIPTION "."
::= { iscsiEntry 3 }
rxMsgs OBJECT-TYPE
     SYNTAX Counter32
     MAX-ACCESS read-only
     STATUS current
     DESCRIPTION "."
::= { iscsiEntry 4 }
rxPingCmdMsgs OBJECT-TYPE
     SYNTAX Counter32
     MAX-ACCESS read-only
     STATUS current
     DESCRIPTION "."
::= { iscsiEntry 5 }
rxScsiCmdMsgs OBJECT-TYPE
     SYNTAX Counter32
     MAX-ACCESS read-only
     STATUS current
     DESCRIPTION "."
::= { iscsiEntry 6 }
rxScsiCmdMsgsRejected OBJECT-TYPE
     SYNTAX Counter32
     MAX-ACCESS read-only
     STATUS current
     DESCRIPTION "."
::= { iscsiEntry 7 }
rxTaskMgtMsgs OBJECT-TYPE
     SYNTAX Counter32
     MAX-ACCESS read-only
     STATUS current
     DESCRIPTION "."
::= { iscsiEntry 8 }
rxTaskMgtMsgsRejected OBJECT-TYPE
     SYNTAX Counter32
     MAX-ACCESS read-only
     STATUS current
     DESCRIPTION "."
::= { iscsiEntry 9 }
rxLoginCmdMsgs OBJECT-TYPE
     SYNTAX Counter32
     MAX-ACCESS read-only
     STATUS current
     DESCRIPTION "."
::= { iscsiEntry 10 }
rxLoginCmdMsgsRejected OBJECT-TYPE
     SYNTAX Counter32
     MAX-ACCESS read-only
     STATUS current
     DESCRIPTION "."
::= { iscsiEntry 11 }
rxTextCmdMsgs OBJECT-TYPE
     SYNTAX Counter32
     MAX-ACCESS read-only
     STATUS current
     DESCRIPTION "."
::= { iscsiEntry 12 }
rxTextCmdMsgsRejected OBJECT-TYPE
     SYNTAX Counter32
     MAX-ACCESS read-only
     STATUS current
     DESCRIPTION "."
::= { iscsiEntry 13 }
rxInvalidMsgs OBJECT-TYPE
     SYNTAX Counter32
     MAX-ACCESS read-only
     STATUS current
     DESCRIPTION "."
::= { iscsiEntry 14 }
rxDataMsgs OBJECT-TYPE
     SYNTAX Counter32
     MAX-ACCESS read-only
     STATUS current
     DESCRIPTION "."
::= { iscsiEntry 15 }
rxDataBytes OBJECT-TYPE
     SYNTAX Counter64
     MAX-ACCESS read-only
     STATUS current
     DESCRIPTION "."
::= { iscsiEntry 16 }
rxDataMsgsDiscarded OBJECT-TYPE
     SYNTAX Counter32
     MAX-ACCESS read-only
     STATUS current
     DESCRIPTION "."
::= { iscsiEntry 17 }
rxDataBytesDiscarded OBJECT-TYPE
     SYNTAX Counter32
     MAX-ACCESS read-only
     STATUS current
     DESCRIPTION "."
::= { iscsiEntry 18 }
txMsgs OBJECT-TYPE
     SYNTAX Counter32
     MAX-ACCESS read-only
     STATUS current
     DESCRIPTION "."
::= { iscsiEntry 19 }
txPingRspMsgs OBJECT-TYPE
     SYNTAX Counter32
     MAX-ACCESS read-only
     STATUS current
     DESCRIPTION "."
::= { iscsiEntry 20 }
txScsiRspMsgs OBJECT-TYPE
     SYNTAX Counter32
     MAX-ACCESS read-only
     STATUS current
     DESCRIPTION "."
::= { iscsiEntry 21 }
txScsiTaskMgtRspMsgs OBJECT-TYPE
     SYNTAX Counter32
     MAX-ACCESS read-only
     STATUS current
     DESCRIPTION "."
::= { iscsiEntry 22 }
txLoginRspMsgs OBJECT-TYPE
     SYNTAX Counter32
     MAX-ACCESS read-only
     STATUS current
     DESCRIPTION "."
::= { iscsiEntry 23 }
txTextRspMsgs OBJECT-TYPE
     SYNTAX Counter32
     MAX-ACCESS read-only
     STATUS current
     DESCRIPTION "."
::= { iscsiEntry 24 }
txRttMsgs OBJECT-TYPE
     SYNTAX Counter32
     MAX-ACCESS read-only
     STATUS current
     DESCRIPTION "."
::= { iscsiEntry 25 }
txAsyncEvtMsgs OBJECT-TYPE
     SYNTAX Counter32
     MAX-ACCESS read-only
     STATUS current
     DESCRIPTION "."
::= { iscsiEntry 26 }
txInvalidOpcodeMsgs OBJECT-TYPE
     SYNTAX Counter32
     MAX-ACCESS read-only
     STATUS current
     DESCRIPTION "."
::= { iscsiEntry 27 }
txDataMsgs OBJECT-TYPE
     SYNTAX Counter32
     MAX-ACCESS read-only
     STATUS current
     DESCRIPTION "."
::= { iscsiEntry 28 }
txDataBytes OBJECT-TYPE
     SYNTAX Counter64
     MAX-ACCESS read-only
     STATUS current
     DESCRIPTION "."
::= { iscsiEntry 29 }
connectionsCreated OBJECT-TYPE
     SYNTAX Counter32
     MAX-ACCESS read-only
     STATUS current
     DESCRIPTION "."
::= { iscsiEntry 30 }
connectionsRefused OBJECT-TYPE
     SYNTAX Counter32
     MAX-ACCESS read-only
     STATUS current
     DESCRIPTION "."
::= { iscsiEntry 31 }
connectionsTerminated OBJECT-TYPE
     SYNTAX Counter32
     MAX-ACCESS read-only
     STATUS current
     DESCRIPTION "."
::= { iscsiEntry 32 }
connectionsErrored OBJECT-TYPE
     SYNTAX Counter32
     MAX-ACCESS read-only
     STATUS current
     DESCRIPTION "."
::= { iscsiEntry 33 }
----------------------------------------------------------------------

iscsiPortTable OBJECT-TYPE
        SYNTAX                       SEQUENCE OF IscsiPortEntry
        MAX-ACCESS                   not-accessible
        STATUS                       current
        DESCRIPTION
            "."
::= { iscsiObjects 3 }

iscsiPortEntry OBJECT-TYPE
        SYNTAX                       IscsiPortEntry
        MAX-ACCESS                   not-accessible
        STATUS                       current
        DESCRIPTION
            "."
        INDEX                        { iscsiIndex, portIpAddress, portTcpPort }
::= { iscsiPortTable 1 }

IscsiPortEntry ::= SEQUENCE {

        portIpAddress                IpAddress,
        portTcpPort                  Unsigned32,
        portIfIndex                  InterfaceIndex,
        hostName                     DisplayString,
        rxPortMsgs                       Counter32,
        rxPortPingCmdMsgs                Counter32,
        rxPortScsiCmdMsgs                Counter32,
        rxPortScsiCmdMsgsRejected        Counter32,
        rxPortTaskMgtMsgs                Counter32,
        rxPortTaskMgtMsgsRejected        Counter32,
        rxPortLoginCmdMsgs               Counter32,
        rxPortLoginCmdMsgsRejected       Counter32,
        rxPortTextCmdMsgs                Counter32,
        rxPortTextCmdMsgsRejected        Counter32,
        rxPortInvalidMsgs                Counter32,
        rxPortDataMsgs                   Counter32,
        rxPortDataBytes                  Counter64,
        rxPortDataMsgsDiscarded          Counter32,
        rxPortDataBytesDiscarded         Counter32,
        txPortMsgs                       Counter32,
        txPortPingRspMsgs                Counter32,
        txPortScsiRspMsgs                Counter32,
        txPortScsiTaskMgtRspMsgs         Counter32,
        txPortLoginRspMsgs               Counter32,
        txPortTextRspMsgs                Counter32,
        txPortRttMsgs                    Counter32,
        txPortAsyncEvtMsgs               Counter32,
        txPortInvalidOpcodeMsgs          Counter32,
        txPortDataMsgs                   Counter32,
        txPortDataBytes                  Counter64
}

portIpAddress OBJECT-TYPE
     SYNTAX IpAddress
     MAX-ACCESS read-only
     STATUS current
     DESCRIPTION "."
::= { iscsiPortEntry 1 }
portTcpPort OBJECT-TYPE
     SYNTAX Unsigned32
     MAX-ACCESS read-only
     STATUS current
     DESCRIPTION "."
::= { iscsiPortEntry 2 }
portIfIndex OBJECT-TYPE
     SYNTAX InterfaceIndex
     MAX-ACCESS read-only
     STATUS current
     DESCRIPTION "."
::= { iscsiPortEntry 3 }
hostName OBJECT-TYPE
     SYNTAX DisplayString
     MAX-ACCESS read-only
     STATUS current
     DESCRIPTION "."
::= { iscsiPortEntry 4 }
rxPortMsgs OBJECT-TYPE
     SYNTAX Counter32
     MAX-ACCESS read-only
     STATUS current
     DESCRIPTION "."
::= { iscsiPortEntry 5 }
rxPortPingCmdMsgs OBJECT-TYPE
     SYNTAX Counter32
     MAX-ACCESS read-only
     STATUS current
     DESCRIPTION "."
::= { iscsiPortEntry 6 }
rxPortScsiCmdMsgs OBJECT-TYPE
     SYNTAX Counter32
     MAX-ACCESS read-only
     STATUS current
     DESCRIPTION "."
::= { iscsiPortEntry 7 }
rxPortScsiCmdMsgsRejected OBJECT-TYPE
     SYNTAX Counter32
     MAX-ACCESS read-only
     STATUS current
     DESCRIPTION "."
::= { iscsiPortEntry 8 }
rxPortTaskMgtMsgs OBJECT-TYPE
     SYNTAX Counter32
     MAX-ACCESS read-only
     STATUS current
     DESCRIPTION "."
::= { iscsiPortEntry 9 }
rxPortTaskMgtMsgsRejected OBJECT-TYPE
     SYNTAX Counter32
     MAX-ACCESS read-only
     STATUS current
     DESCRIPTION "."
::= { iscsiPortEntry 10 }
rxPortLoginCmdMsgs OBJECT-TYPE
     SYNTAX Counter32
     MAX-ACCESS read-only
     STATUS current
     DESCRIPTION "."
::= { iscsiPortEntry 11 }
rxPortLoginCmdMsgsRejected OBJECT-TYPE
     SYNTAX Counter32
     MAX-ACCESS read-only
     STATUS current
     DESCRIPTION "."
::= { iscsiPortEntry 12 }
rxPortTextCmdMsgs OBJECT-TYPE
     SYNTAX Counter32
     MAX-ACCESS read-only
     STATUS current
     DESCRIPTION "."
::= { iscsiPortEntry 13 }
rxPortTextCmdMsgsRejected OBJECT-TYPE
     SYNTAX Counter32
     MAX-ACCESS read-only
     STATUS current
     DESCRIPTION "."
::= { iscsiPortEntry 14 }
rxPortInvalidMsgs OBJECT-TYPE
     SYNTAX Counter32
     MAX-ACCESS read-only
     STATUS current
     DESCRIPTION "."
::= { iscsiPortEntry 15 }
rxPortDataMsgs OBJECT-TYPE
     SYNTAX Counter32
     MAX-ACCESS read-only
     STATUS current
     DESCRIPTION "."
::= { iscsiPortEntry 16 }
rxPortDataBytes OBJECT-TYPE
     SYNTAX Counter64
     MAX-ACCESS read-only
     STATUS current
     DESCRIPTION "."
::= { iscsiPortEntry 17 }
rxPortDataMsgsDiscarded OBJECT-TYPE
     SYNTAX Counter32
     MAX-ACCESS read-only
     STATUS current
     DESCRIPTION "."
::= { iscsiPortEntry 18 }
rxPortDataBytesDiscarded OBJECT-TYPE
     SYNTAX Counter32
     MAX-ACCESS read-only
     STATUS current
     DESCRIPTION "."
::= { iscsiPortEntry 19 }
txPortMsgs OBJECT-TYPE
     SYNTAX Counter32
     MAX-ACCESS read-only
     STATUS current
     DESCRIPTION "."
::= { iscsiPortEntry 20 }
txPortPingRspMsgs OBJECT-TYPE
     SYNTAX Counter32
     MAX-ACCESS read-only
     STATUS current
     DESCRIPTION "."
::= { iscsiPortEntry 21 }
txPortScsiRspMsgs OBJECT-TYPE
     SYNTAX Counter32
     MAX-ACCESS read-only
     STATUS current
     DESCRIPTION "."
::= { iscsiPortEntry 22 }
txPortScsiTaskMgtRspMsgs OBJECT-TYPE
     SYNTAX Counter32
     MAX-ACCESS read-only
     STATUS current
     DESCRIPTION "."
::= { iscsiPortEntry 23 }
txPortLoginRspMsgs OBJECT-TYPE
     SYNTAX Counter32
     MAX-ACCESS read-only
     STATUS current
     DESCRIPTION "."
::= { iscsiPortEntry 24 }
txPortTextRspMsgs OBJECT-TYPE
     SYNTAX Counter32
     MAX-ACCESS read-only
     STATUS current
     DESCRIPTION "."
::= { iscsiPortEntry 25 }
txPortRttMsgs OBJECT-TYPE
     SYNTAX Counter32
     MAX-ACCESS read-only
     STATUS current
     DESCRIPTION "."
::= { iscsiPortEntry 26 }
txPortAsyncEvtMsgs OBJECT-TYPE
     SYNTAX Counter32
     MAX-ACCESS read-only
     STATUS current
     DESCRIPTION "."
::= { iscsiPortEntry 27 }
txPortInvalidOpcodeMsgs OBJECT-TYPE
     SYNTAX Counter32
     MAX-ACCESS read-only
     STATUS current
     DESCRIPTION "."
::= { iscsiPortEntry 28 }
txPortDataMsgs OBJECT-TYPE
     SYNTAX Counter32
     MAX-ACCESS read-only
     STATUS current
     DESCRIPTION "."
::= { iscsiPortEntry 29 }
txPortDataBytes OBJECT-TYPE
     SYNTAX Counter64
     MAX-ACCESS read-only
     STATUS current
     DESCRIPTION "."
::= { iscsiPortEntry 30 }
----------------------------------------------------------------------

iscsiTargetTable OBJECT-TYPE
        SYNTAX                       SEQUENCE OF IscsiTargetEntry
        MAX-ACCESS                   not-accessible
        STATUS                       current
        DESCRIPTION
            "."
::= { iscsiObjects 4 }

iscsiTargetEntry OBJECT-TYPE
        SYNTAX                       IscsiTargetEntry
        MAX-ACCESS                   not-accessible
        STATUS                       current
        DESCRIPTION
            "."
        INDEX                        { iscsiIndex, targetIndex }
::= { iscsiTargetTable 1 }

IscsiTargetEntry ::= SEQUENCE {

        targetIndex           Unsigned32,
        targetName            DisplayString,
     targetLunNumber               Unsigned32,
        rxTargetMsgs                    Counter32,
        rxTargetScsiCmdMsgs             Counter32,
        rxTargetScsiCmdMsgsRejected     Counter32,
        rxTargetTaskMgtMsgs             Counter32,
        rxTargetTaskMgtMsgsRejected     Counter32,
        rxTargetLoginCmdMsgs            Counter32,
        rxTargetLoginCmdMsgsRejected    Counter32,
        rxTargetDataMsgs                Counter32,
        rxTargetDataBytes               Counter64,
        rxTargetDataMsgsDiscarded       Counter32,
        rxTargetDataBytesDiscarded      Counter32,
        txTargetMsgs                    Counter32,
        txTargetScsiRspMsgs             Counter32,
        txTargetScsiTaskMgtRspMsgs      Counter32,
        txTargetLoginRspMsgs            Counter32,
        txTargetRttMsgs                 Counter32,
        txTargetAsyncEvtMsgs            Counter32,
        txTargetDataMsgs                Counter32,
        txTargetDataBytes               Counter64
}

targetIndex OBJECT-TYPE
     SYNTAX Unsigned32
     MAX-ACCESS read-only
     STATUS current
     DESCRIPTION "."
::= { iscsiTargetEntry 1 }
targetName OBJECT-TYPE
     SYNTAX DisplayString
     MAX-ACCESS read-only
     STATUS current
     DESCRIPTION "."
::= { iscsiTargetEntry 2 }
targetLunNumber OBJECT-TYPE
    SYNTAX Unsigned32
    MAX-ACCESS read-only
    STATUS current
     DESCRIPTION "."
::= { iscsiTargetEntry 3 }
rxTargetMsgs OBJECT-TYPE
     SYNTAX Counter32
     MAX-ACCESS read-only
     STATUS current
     DESCRIPTION "."
::= { iscsiTargetEntry 4 }
rxTargetScsiCmdMsgs OBJECT-TYPE
     SYNTAX Counter32
     MAX-ACCESS read-only
     STATUS current
     DESCRIPTION "."
::= { iscsiTargetEntry 5 }
rxTargetScsiCmdMsgsRejected OBJECT-TYPE
     SYNTAX Counter32
     MAX-ACCESS read-only
     STATUS current
     DESCRIPTION "."
::= { iscsiTargetEntry 6 }
rxTargetTaskMgtMsgs OBJECT-TYPE
     SYNTAX Counter32
     MAX-ACCESS read-only
     STATUS current
     DESCRIPTION "."
::= { iscsiTargetEntry 7 }
rxTargetTaskMgtMsgsRejected OBJECT-TYPE
     SYNTAX Counter32
     MAX-ACCESS read-only
     STATUS current
     DESCRIPTION "."
::= { iscsiTargetEntry 8 }
rxTargetLoginCmdMsgs OBJECT-TYPE
     SYNTAX Counter32
     MAX-ACCESS read-only
     STATUS current
     DESCRIPTION "."
::= { iscsiTargetEntry 9 }
rxTargetLoginCmdMsgsRejected OBJECT-TYPE
     SYNTAX Counter32
     MAX-ACCESS read-only
     STATUS current
     DESCRIPTION "."
::= { iscsiTargetEntry 10 }
rxTargetDataMsgs OBJECT-TYPE
     SYNTAX Counter32
     MAX-ACCESS read-only
     STATUS current
     DESCRIPTION "."
::= { iscsiTargetEntry 11 }
rxTargetDataBytes OBJECT-TYPE
     SYNTAX Counter64
     MAX-ACCESS read-only
     STATUS current
     DESCRIPTION "."
::= { iscsiTargetEntry 12 }
rxTargetDataMsgsDiscarded OBJECT-TYPE
     SYNTAX Counter32
     MAX-ACCESS read-only
     STATUS current
     DESCRIPTION "."
::= { iscsiTargetEntry 13 }
rxTargetDataBytesDiscarded OBJECT-TYPE
     SYNTAX Counter32
     MAX-ACCESS read-only
     STATUS current
     DESCRIPTION "."
::= { iscsiTargetEntry 14 }
txTargetMsgs OBJECT-TYPE
     SYNTAX Counter32
     MAX-ACCESS read-only
     STATUS current
     DESCRIPTION "."
::= { iscsiTargetEntry 15 }
txTargetScsiRspMsgs OBJECT-TYPE
     SYNTAX Counter32
     MAX-ACCESS read-only
     STATUS current
     DESCRIPTION "."
::= { iscsiTargetEntry 16 }
txTargetScsiTaskMgtRspMsgs OBJECT-TYPE
     SYNTAX Counter32
     MAX-ACCESS read-only
     STATUS current
     DESCRIPTION "."
::= { iscsiTargetEntry 17 }
txTargetLoginRspMsgs OBJECT-TYPE
     SYNTAX Counter32
     MAX-ACCESS read-only
     STATUS current
     DESCRIPTION "."
::= { iscsiTargetEntry 18 }
txTargetRttMsgs OBJECT-TYPE
     SYNTAX Counter32
     MAX-ACCESS read-only
     STATUS current
     DESCRIPTION "."
::= { iscsiTargetEntry 19 }
txTargetAsyncEvtMsgs OBJECT-TYPE
     SYNTAX Counter32
     MAX-ACCESS read-only
     STATUS current
     DESCRIPTION "."
::= { iscsiTargetEntry 20 }
txTargetDataMsgs OBJECT-TYPE
     SYNTAX Counter32
     MAX-ACCESS read-only
     STATUS current
     DESCRIPTION "."
::= { iscsiTargetEntry 21 }
txTargetDataBytes OBJECT-TYPE
     SYNTAX Counter64
     MAX-ACCESS read-only
     STATUS current
     DESCRIPTION "."
::= { iscsiTargetEntry 22 }
----------------------------------------------------------------------

iscsiLunTable OBJECT-TYPE
        SYNTAX                       SEQUENCE OF IscsiLunEntry
        MAX-ACCESS                   not-accessible
        STATUS                       current
        DESCRIPTION
            "."
::= { iscsiObjects 5 }

iscsiLunEntry OBJECT-TYPE
        SYNTAX                       IscsiLunEntry
        MAX-ACCESS                   not-accessible
        STATUS                       current
        DESCRIPTION
            "."
        INDEX                        { iscsiIndex, targetIndex, lunId }
::= { iscsiLunTable 1 }

IscsiLunEntry ::= SEQUENCE {

        lunId                        Unsigned32,
     lunSerialNumber               DisplayString,
        rxLunMsgs                       Counter32,
        rxLunScsiCmdMsgs                Counter32,
        rxLunScsiCmdMsgsRejected        Counter32,
        rxLunTaskMgtMsgs                Counter32,
        rxLunTaskMgtMsgsRejected        Counter32,
        rxLunDataMsgs                   Counter32,
        rxLunDataBytes                  Counter64,
        rxLunDataMsgsDiscarded          Counter32,
        rxLunDataBytesDiscarded         Counter32,
        txLunMsgs                       Counter32,
        txLunScsiRspMsgs                Counter32,
        txLunScsiTaskMgtRspMsgs         Counter32,
        txLunAsyncEvtMsgs               Counter32,
        txLunDataMsgs                   Counter32,
        txLunDataBytes                  Counter64,
     lunInquiryString         DisplayString
}

lunId OBJECT-TYPE
     SYNTAX Unsigned32
     MAX-ACCESS read-only
     STATUS current
     DESCRIPTION "."
::= { iscsiLunEntry 1 }
lunSerialNumber OBJECT-TYPE
     SYNTAX DisplayString
     MAX-ACCESS read-only
     STATUS current
     DESCRIPTION "."
::= { iscsiLunEntry 2 }
rxLunMsgs OBJECT-TYPE
     SYNTAX Counter32
     MAX-ACCESS read-only
     STATUS current
     DESCRIPTION "."
::= { iscsiLunEntry 3 }
rxLunScsiCmdMsgs OBJECT-TYPE
     SYNTAX Counter32
     MAX-ACCESS read-only
     STATUS current
     DESCRIPTION "."
::= { iscsiLunEntry 4 }
rxLunScsiCmdMsgsRejected OBJECT-TYPE
     SYNTAX Counter32
     MAX-ACCESS read-only
     STATUS current
     DESCRIPTION "."
::= { iscsiLunEntry 5 }
rxLunTaskMgtMsgs OBJECT-TYPE
     SYNTAX Counter32
     MAX-ACCESS read-only
     STATUS current
     DESCRIPTION "."
::= { iscsiLunEntry 6 }
rxLunTaskMgtMsgsRejected OBJECT-TYPE
     SYNTAX Counter32
     MAX-ACCESS read-only
     STATUS current
     DESCRIPTION "."
::= { iscsiLunEntry 7 }
rxLunDataMsgs OBJECT-TYPE
     SYNTAX Counter32
     MAX-ACCESS read-only
     STATUS current
     DESCRIPTION "."
::= { iscsiLunEntry 8 }
rxLunDataBytes OBJECT-TYPE
     SYNTAX Counter64
     MAX-ACCESS read-only
     STATUS current
     DESCRIPTION "."
::= { iscsiLunEntry 9 }
rxLunDataMsgsDiscarded OBJECT-TYPE
     SYNTAX Counter32
     MAX-ACCESS read-only
     STATUS current
     DESCRIPTION "."
::= { iscsiLunEntry 10 }
rxLunDataBytesDiscarded OBJECT-TYPE
     SYNTAX Counter32
     MAX-ACCESS read-only
     STATUS current
     DESCRIPTION "."
::= { iscsiLunEntry 11 }
txLunMsgs OBJECT-TYPE
     SYNTAX Counter32
     MAX-ACCESS read-only
     STATUS current
     DESCRIPTION "."
::= { iscsiLunEntry 12 }
txLunScsiRspMsgs OBJECT-TYPE
     SYNTAX Counter32
     MAX-ACCESS read-only
     STATUS current
     DESCRIPTION "."
::= { iscsiLunEntry 13 }
txLunScsiTaskMgtRspMsgs OBJECT-TYPE
     SYNTAX Counter32
     MAX-ACCESS read-only
     STATUS current
     DESCRIPTION "."
::= { iscsiLunEntry 14 }
txLunAsyncEvtMsgs OBJECT-TYPE
     SYNTAX Counter32
     MAX-ACCESS read-only
     STATUS current
     DESCRIPTION "."
::= { iscsiLunEntry 15 }
txLunDataMsgs OBJECT-TYPE
     SYNTAX Counter32
     MAX-ACCESS read-only
     STATUS current
     DESCRIPTION "."
::= { iscsiLunEntry 16 }
txLunDataBytes OBJECT-TYPE
     SYNTAX Counter64
     MAX-ACCESS read-only
     STATUS current
     DESCRIPTION "."
::= { iscsiLunEntry 17 }
lunInquiryString OBJECT-TYPE
     SYNTAX DisplayString
     MAX-ACCESS read-only
     STATUS current
     DESCRIPTION "."
::= { iscsiLunEntry 18 }
----------------------------------------------------------------------

iscsiInitiatorTable OBJECT-TYPE
        SYNTAX                       SEQUENCE OF IscsiInitiatorEntry
        MAX-ACCESS                   not-accessible
        STATUS                       current
        DESCRIPTION
            "."
::= { iscsiObjects 6 }

iscsiInitiatorEntry OBJECT-TYPE
        SYNTAX                       IscsiInitiatorEntry
        MAX-ACCESS                   not-accessible
        STATUS                       current
        DESCRIPTION
            "."
        INDEX         { iscsiIndex, initiatorIndex }
::= { iscsiInitiatorTable 1 }

IscsiInitiatorEntry ::= SEQUENCE {

        initiatorIndex               Unsigned32,
        initiatorName                    DisplayString,
        status                       INTEGER,
        connections                  Unsigned32,
        rxInitiatorMsgs                       Counter32,
        rxInitiatorPingCmdMsgs                Counter32,
        rxInitiatorScsiCmdMsgs                Counter32,
        rxInitiatorScsiCmdMsgsRejected        Counter32,
        rxInitiatorTaskMgtMsgs                Counter32,
        rxInitiatorTaskMgtMsgsRejected        Counter32,
        rxInitiatorLoginCmdMsgs               Counter32,
        rxInitiatorLoginCmdMsgsRejected       Counter32,
        rxInitiatorTextCmdMsgs                Counter32,
        rxInitiatorTextCmdMsgsRejected        Counter32,
        rxInitiatorInvalidMsgs                Counter32,
        rxInitiatorDataMsgs                   Counter32,
        rxInitiatorDataBytes                  Counter64,
        rxInitiatorDataMsgsDiscarded          Counter32,
        rxInitiatorDataBytesDiscarded         Counter32,
        txInitiatorMsgs                       Counter32,
        txInitiatorPingRspMsgs                Counter32,
        txInitiatorScsiRspMsgs                Counter32,
        txInitiatorScsiTaskMgtRspMsgs         Counter32,
        txInitiatorLoginRspMsgs               Counter32,
        txInitiatorTextRspMsgs                Counter32,
        txInitiatorRttMsgs                    Counter32,
        txInitiatorAsyncEvtMsgs               Counter32,
        txInitiatorInvalidOpcodeMsgs          Counter32,
        txInitiatorDataMsgs                   Counter32,
        txInitiatorDataBytes                  Counter64
}

initiatorIndex OBJECT-TYPE
     SYNTAX Unsigned32
     MAX-ACCESS read-only
     STATUS current
     DESCRIPTION "."
::= { iscsiInitiatorEntry 1 }
initiatorName OBJECT-TYPE
     SYNTAX DisplayString
     MAX-ACCESS read-only
     STATUS current
     DESCRIPTION "."
::= { iscsiInitiatorEntry 2 }
status OBJECT-TYPE
     SYNTAX INTEGER { someStatus (1), someOtherStatus (2) }
     MAX-ACCESS read-only
     STATUS current
     DESCRIPTION "."
::= { iscsiInitiatorEntry 3 }
connections OBJECT-TYPE
     SYNTAX Unsigned32
     MAX-ACCESS read-only
     STATUS current
     DESCRIPTION "."
::= { iscsiInitiatorEntry 4 }
rxInitiatorMsgs OBJECT-TYPE
     SYNTAX Counter32
     MAX-ACCESS read-only
     STATUS current
     DESCRIPTION "."
::= { iscsiInitiatorEntry 5 }
rxInitiatorPingCmdMsgs OBJECT-TYPE
     SYNTAX Counter32
     MAX-ACCESS read-only
     STATUS current
     DESCRIPTION "."
::= { iscsiInitiatorEntry 6 }
rxInitiatorScsiCmdMsgs OBJECT-TYPE
     SYNTAX Counter32
     MAX-ACCESS read-only
     STATUS current
     DESCRIPTION "."
::= { iscsiInitiatorEntry 7 }
rxInitiatorScsiCmdMsgsRejected OBJECT-TYPE
     SYNTAX Counter32
     MAX-ACCESS read-only
     STATUS current
     DESCRIPTION "."
::= { iscsiInitiatorEntry 8}
rxInitiatorTaskMgtMsgs OBJECT-TYPE
     SYNTAX Counter32
     MAX-ACCESS read-only
     STATUS current
     DESCRIPTION "."
::= { iscsiInitiatorEntry 9 }
rxInitiatorTaskMgtMsgsRejected OBJECT-TYPE
     SYNTAX Counter32
     MAX-ACCESS read-only
     STATUS current
     DESCRIPTION "."
::= { iscsiInitiatorEntry 10 }
rxInitiatorLoginCmdMsgs OBJECT-TYPE
     SYNTAX Counter32
     MAX-ACCESS read-only
     STATUS current
     DESCRIPTION "."
::= { iscsiInitiatorEntry 11 }
rxInitiatorLoginCmdMsgsRejected OBJECT-TYPE
     SYNTAX Counter32
     MAX-ACCESS read-only
     STATUS current
     DESCRIPTION "."
::= { iscsiInitiatorEntry 12 }
rxInitiatorTextCmdMsgs OBJECT-TYPE
     SYNTAX Counter32
     MAX-ACCESS read-only
     STATUS current
     DESCRIPTION "."
::= { iscsiInitiatorEntry 13 }
rxInitiatorTextCmdMsgsRejected OBJECT-TYPE
     SYNTAX Counter32
     MAX-ACCESS read-only
     STATUS current
     DESCRIPTION "."
::= { iscsiInitiatorEntry 14 }
rxInitiatorInvalidMsgs OBJECT-TYPE
     SYNTAX Counter32
     MAX-ACCESS read-only
     STATUS current
     DESCRIPTION "."
::= { iscsiInitiatorEntry 15 }
rxInitiatorDataMsgs OBJECT-TYPE
     SYNTAX Counter32
     MAX-ACCESS read-only
     STATUS current
     DESCRIPTION "."
::= { iscsiInitiatorEntry 16 }
rxInitiatorDataBytes OBJECT-TYPE
     SYNTAX Counter64
     MAX-ACCESS read-only
     STATUS current
     DESCRIPTION "."
::= { iscsiInitiatorEntry 17 }
rxInitiatorDataMsgsDiscarded OBJECT-TYPE
     SYNTAX Counter32
     MAX-ACCESS read-only
     STATUS current
     DESCRIPTION "."
::= { iscsiInitiatorEntry 18 }
rxInitiatorDataBytesDiscarded OBJECT-TYPE
     SYNTAX Counter32
     MAX-ACCESS read-only
     STATUS current
     DESCRIPTION "."
::= { iscsiInitiatorEntry 19 }
txInitiatorMsgs OBJECT-TYPE
     SYNTAX Counter32
     MAX-ACCESS read-only
     STATUS current
     DESCRIPTION "."
::= { iscsiInitiatorEntry 20 }
txInitiatorPingRspMsgs OBJECT-TYPE
     SYNTAX Counter32
     MAX-ACCESS read-only
     STATUS current
     DESCRIPTION "."
::= { iscsiInitiatorEntry 21 }
txInitiatorScsiRspMsgs OBJECT-TYPE
     SYNTAX Counter32
     MAX-ACCESS read-only
     STATUS current
     DESCRIPTION "."
::= { iscsiInitiatorEntry 22 }
txInitiatorScsiTaskMgtRspMsgs OBJECT-TYPE
     SYNTAX Counter32
     MAX-ACCESS read-only
     STATUS current
     DESCRIPTION "."
::= { iscsiInitiatorEntry 23 }
txInitiatorLoginRspMsgs OBJECT-TYPE
     SYNTAX Counter32
     MAX-ACCESS read-only
     STATUS current
     DESCRIPTION "."
::= { iscsiInitiatorEntry 24 }
txInitiatorTextRspMsgs OBJECT-TYPE
     SYNTAX Counter32
     MAX-ACCESS read-only
     STATUS current
     DESCRIPTION "."
::= { iscsiInitiatorEntry 25 }
txInitiatorRttMsgs OBJECT-TYPE
     SYNTAX Counter32
     MAX-ACCESS read-only
     STATUS current
     DESCRIPTION "."
::= { iscsiInitiatorEntry 26 }
txInitiatorAsyncEvtMsgs OBJECT-TYPE
     SYNTAX Counter32
     MAX-ACCESS read-only
     STATUS current
     DESCRIPTION "."
::= { iscsiInitiatorEntry 27 }
txInitiatorInvalidOpcodeMsgs OBJECT-TYPE
     SYNTAX Counter32
     MAX-ACCESS read-only
     STATUS current
     DESCRIPTION "."
::= { iscsiInitiatorEntry 28 }
txInitiatorDataMsgs OBJECT-TYPE
     SYNTAX Counter32
     MAX-ACCESS read-only
     STATUS current
     DESCRIPTION "."
::= { iscsiInitiatorEntry 29 }
txInitiatorDataBytes OBJECT-TYPE
     SYNTAX Counter64
     MAX-ACCESS read-only
     STATUS current
     DESCRIPTION "."
::= { iscsiInitiatorEntry 30 }

----------------------------------------------------------------------

iscsiCxnTable OBJECT-TYPE
        SYNTAX                       SEQUENCE OF IscsiCxnEntry
        MAX-ACCESS                   not-accessible
        STATUS                       current
        DESCRIPTION
            "."
::= { iscsiObjects 7 }

iscsiCxnEntry OBJECT-TYPE
        SYNTAX                       IscsiCxnEntry
        MAX-ACCESS                   not-accessible
        STATUS                       current
        DESCRIPTION
            "."
        INDEX         { iscsiIndex, initiatorIndex, cxnIpAddress, cxnTcpPort }
::= { iscsiCxnTable 1 }

IscsiCxnEntry ::= SEQUENCE {

        cxnIpAddress                 IpAddress,
        cxnTcpPort                   Unsigned32,
        isid                         Unsigned32,  -- Session ID (0..65535)
        tsid                         Unsigned32,  -- Session ID (0..65535)
        state                        IScsiConnectState,
        allowNoRtt                   INTEGER,     -- (0 == No; 1 == Yes)
        initiator                    DisplayString,
        authenticator                DisplayString,
        authType                     IScsiAuthType,
        msgCheckType                 IScsiCheckType,
        dataCheckType                IScsiCheckType,
        rxCxnMsgs                       Counter32,
        rxCxnPingCmdMsgs                Counter32,
        rxCxnScsiCmdMsgs                Counter32,
        rxCxnScsiCmdMsgsRejected        Counter32,
        rxCxnTaskMgtMsgs                Counter32,
        rxCxnTaskMgtMsgsRejected        Counter32,
        rxCxnLoginCmdMsgs               Counter32,
        rxCxnLoginCmdMsgsRejected       Counter32,
        rxCxnTextCmdMsgs                Counter32,
        rxCxnTextCmdMsgsRejected        Counter32,
        rxCxnInvalidMsgs                Counter32,
        rxCxnDataMsgs                   Counter32,
        rxCxnDataBytes                  Counter64,
        rxCxnDataMsgsDiscarded          Counter32,
        rxCxnDataBytesDiscarded         Counter32,
        txCxnMsgs                       Counter32,
        txCxnPingRspMsgs                Counter32,
        txCxnScsiRspMsgs                Counter32,
        txCxnScsiTaskMgtRspMsgs         Counter32,
        txCxnLoginRspMsgs               Counter32,
        txCxnTextRspMsgs                Counter32,
        txCxnRttMsgs                    Counter32,
        txCxnAsyncEvtMsgs               Counter32,
        txCxnInvalidOpcodeMsgs          Counter32,
        txCxnDataMsgs                   Counter32,
        txCxnDataBytes                  Counter64
}

cxnIpAddress OBJECT-TYPE
     SYNTAX IpAddress
     MAX-ACCESS read-only
     STATUS current
     DESCRIPTION "."
::= { iscsiCxnEntry 1 }
cxnTcpPort OBJECT-TYPE
     SYNTAX Unsigned32
     MAX-ACCESS read-only
     STATUS current
     DESCRIPTION "."
::= { iscsiCxnEntry 2 }
isid OBJECT-TYPE
     SYNTAX Unsigned32 (0..65535)
     MAX-ACCESS read-only
     STATUS current
     DESCRIPTION "."
::= { iscsiCxnEntry 3 }
tsid OBJECT-TYPE
     SYNTAX Unsigned32 (0..65535)
     MAX-ACCESS read-only
     STATUS current
     DESCRIPTION "."
::= { iscsiCxnEntry 4 }
state OBJECT-TYPE
     SYNTAX IScsiConnectState
     MAX-ACCESS read-only
     STATUS current
     DESCRIPTION "."
::= { iscsiCxnEntry 5 }
allowNoRtt OBJECT-TYPE
     SYNTAX INTEGER { no (1), yes (2) }
     MAX-ACCESS read-only
     STATUS current
     DESCRIPTION "."
::= { iscsiCxnEntry 6 }
initiator OBJECT-TYPE
     SYNTAX DisplayString
     MAX-ACCESS read-only
     STATUS current
     DESCRIPTION "."
::= { iscsiCxnEntry 7 }
authenticator OBJECT-TYPE
     SYNTAX DisplayString
     MAX-ACCESS read-only
     STATUS current
     DESCRIPTION "."
::= { iscsiCxnEntry 8 }
authType OBJECT-TYPE
     SYNTAX IScsiAuthType
     MAX-ACCESS read-only
     STATUS current
     DESCRIPTION "."
::= { iscsiCxnEntry 9 }
msgCheckType OBJECT-TYPE
     SYNTAX IScsiCheckType
     MAX-ACCESS read-only
     STATUS current
     DESCRIPTION "."
::= { iscsiCxnEntry 10 }
dataCheckType OBJECT-TYPE
     SYNTAX IScsiCheckType
     MAX-ACCESS read-only
     STATUS current
     DESCRIPTION "."
::= { iscsiCxnEntry 11 }
rxCxnMsgs OBJECT-TYPE
     SYNTAX Counter32
     MAX-ACCESS read-only
     STATUS current
     DESCRIPTION "."
::= { iscsiCxnEntry 12 }
rxCxnPingCmdMsgs OBJECT-TYPE
     SYNTAX Counter32
     MAX-ACCESS read-only
     STATUS current
     DESCRIPTION "."
::= { iscsiCxnEntry 13 }
rxCxnScsiCmdMsgs OBJECT-TYPE
     SYNTAX Counter32
     MAX-ACCESS read-only
     STATUS current
     DESCRIPTION "."
::= { iscsiCxnEntry 14 }
rxCxnScsiCmdMsgsRejected OBJECT-TYPE
     SYNTAX Counter32
     MAX-ACCESS read-only
     STATUS current
     DESCRIPTION "."
::= { iscsiCxnEntry 15 }
rxCxnTaskMgtMsgs OBJECT-TYPE
     SYNTAX Counter32
     MAX-ACCESS read-only
     STATUS current
     DESCRIPTION "."
::= { iscsiCxnEntry 16 }
rxCxnTaskMgtMsgsRejected OBJECT-TYPE
     SYNTAX Counter32
     MAX-ACCESS read-only
     STATUS current
     DESCRIPTION "."
::= { iscsiCxnEntry 17 }
rxCxnLoginCmdMsgs OBJECT-TYPE
     SYNTAX Counter32
     MAX-ACCESS read-only
     STATUS current
     DESCRIPTION "."
::= { iscsiCxnEntry 18 }
rxCxnLoginCmdMsgsRejected OBJECT-TYPE
     SYNTAX Counter32
     MAX-ACCESS read-only
     STATUS current
     DESCRIPTION "."
::= { iscsiCxnEntry 19 }
rxCxnTextCmdMsgs OBJECT-TYPE
     SYNTAX Counter32
     MAX-ACCESS read-only
     STATUS current
     DESCRIPTION "."
::= { iscsiCxnEntry 20 }
rxCxnTextCmdMsgsRejected OBJECT-TYPE
     SYNTAX Counter32
     MAX-ACCESS read-only
     STATUS current
     DESCRIPTION "."
::= { iscsiCxnEntry 21 }
rxCxnInvalidMsgs OBJECT-TYPE
     SYNTAX Counter32
     MAX-ACCESS read-only
     STATUS current
     DESCRIPTION "."
::= { iscsiCxnEntry 22 }
rxCxnDataMsgs OBJECT-TYPE
     SYNTAX Counter32
     MAX-ACCESS read-only
     STATUS current
     DESCRIPTION "."
::= { iscsiCxnEntry 23 }
rxCxnDataBytes OBJECT-TYPE
     SYNTAX Counter64
     MAX-ACCESS read-only
     STATUS current
     DESCRIPTION "."
::= { iscsiCxnEntry 24 }
rxCxnDataMsgsDiscarded OBJECT-TYPE
     SYNTAX Counter32
     MAX-ACCESS read-only
     STATUS current
     DESCRIPTION "."
::= { iscsiCxnEntry 25 }
rxCxnDataBytesDiscarded OBJECT-TYPE
     SYNTAX Counter32
     MAX-ACCESS read-only
     STATUS current
     DESCRIPTION "."
::= { iscsiCxnEntry 26 }
txCxnMsgs OBJECT-TYPE
     SYNTAX Counter32
     MAX-ACCESS read-only
     STATUS current
     DESCRIPTION "."
::= { iscsiCxnEntry 27 }
txCxnPingRspMsgs OBJECT-TYPE
     SYNTAX Counter32
     MAX-ACCESS read-only
     STATUS current
     DESCRIPTION "."
::= { iscsiCxnEntry 28 }
txCxnScsiRspMsgs OBJECT-TYPE
     SYNTAX Counter32
     MAX-ACCESS read-only
     STATUS current
     DESCRIPTION "."
::= { iscsiCxnEntry 29 }
txCxnScsiTaskMgtRspMsgs OBJECT-TYPE
     SYNTAX Counter32
     MAX-ACCESS read-only
     STATUS current
     DESCRIPTION "."
::= { iscsiCxnEntry 30 }
txCxnLoginRspMsgs OBJECT-TYPE
     SYNTAX Counter32
     MAX-ACCESS read-only
     STATUS current
     DESCRIPTION "."
::= { iscsiCxnEntry 31 }
txCxnTextRspMsgs OBJECT-TYPE
     SYNTAX Counter32
     MAX-ACCESS read-only
     STATUS current
     DESCRIPTION "."
::= { iscsiCxnEntry 32 }
txCxnRttMsgs OBJECT-TYPE
     SYNTAX Counter32
     MAX-ACCESS read-only
     STATUS current
     DESCRIPTION "."
::= { iscsiCxnEntry 33 }
txCxnAsyncEvtMsgs OBJECT-TYPE
     SYNTAX Counter32
     MAX-ACCESS read-only
     STATUS current
     DESCRIPTION "."
::= { iscsiCxnEntry 34 }
txCxnInvalidOpcodeMsgs OBJECT-TYPE
     SYNTAX Counter32
     MAX-ACCESS read-only
     STATUS current
     DESCRIPTION "."
::= { iscsiCxnEntry 35 }
txCxnDataMsgs OBJECT-TYPE
     SYNTAX Counter32
     MAX-ACCESS read-only
     STATUS current
     DESCRIPTION "."
::= { iscsiCxnEntry 36 }
txCxnDataBytes OBJECT-TYPE
     SYNTAX Counter64
     MAX-ACCESS read-only
     STATUS current
     DESCRIPTION "."
::= { iscsiCxnEntry 37 }

----------------------------------------------------------------------

iscsiGroups OBJECT IDENTIFIER ::= { iscsiConformance 1 }

iscsiGeneralInfoGroup OBJECT-GROUP
    OBJECTS {
        iscsiNumber,
        iscsiIndex,
        iscsiName,
        iscsiDescription,
        rxMsgs,
        rxPingCmdMsgs,
        rxScsiCmdMsgs,
        rxScsiCmdMsgsRejected,
        rxTaskMgtMsgs,
        rxTaskMgtMsgsRejected,
        rxLoginCmdMsgs,
        rxLoginCmdMsgsRejected,
        rxTextCmdMsgs,
        rxTextCmdMsgsRejected,
        rxInvalidMsgs,
        rxDataMsgs,
        rxDataBytes,
        rxDataMsgsDiscarded,
        rxDataBytesDiscarded,
        txMsgs,
        txPingRspMsgs,
        txScsiRspMsgs,
        txScsiTaskMgtRspMsgs,
        txLoginRspMsgs,
        txTextRspMsgs,
        txRttMsgs,
        txAsyncEvtMsgs,
        txInvalidOpcodeMsgs,
        txDataMsgs,
        txDataBytes,
        connectionsCreated,
        connectionsRefused,
        connectionsTerminated,
        connectionsErrored
     }
    STATUS current
    DESCRIPTION "."

::= { iscsiGroups 1 }

iscsiPortInfoGroup OBJECT-GROUP
    OBJECTS {
        portIpAddress,
        portTcpPort,
        portIfIndex,
        hostName,
        rxPortMsgs,
        rxPortPingCmdMsgs,
        rxPortScsiCmdMsgs,
        rxPortScsiCmdMsgsRejected,
        rxPortTaskMgtMsgs,
        rxPortTaskMgtMsgsRejected,
        rxPortLoginCmdMsgs,
        rxPortLoginCmdMsgsRejected,
        rxPortTextCmdMsgs,
        rxPortTextCmdMsgsRejected,
        rxPortInvalidMsgs,
        rxPortDataMsgs,
        rxPortDataBytes,
        rxPortDataMsgsDiscarded,
        rxPortDataBytesDiscarded,
        txPortMsgs,
        txPortPingRspMsgs,
        txPortScsiRspMsgs,
        txPortScsiTaskMgtRspMsgs,
        txPortLoginRspMsgs,
        txPortTextRspMsgs,
        txPortRttMsgs,
        txPortAsyncEvtMsgs,
        txPortInvalidOpcodeMsgs,
        txPortDataMsgs,
        txPortDataBytes
     }
    STATUS current
    DESCRIPTION "."

::= { iscsiGroups 2 }
iscsiTargetInfoGroup OBJECT-GROUP
    OBJECTS {
        targetIndex,
        targetName,
     targetLunNumber,
        rxTargetMsgs,
        rxTargetScsiCmdMsgs,
        rxTargetScsiCmdMsgsRejected,
        rxTargetTaskMgtMsgs,
        rxTargetTaskMgtMsgsRejected,
        rxTargetLoginCmdMsgs,
        rxTargetLoginCmdMsgsRejected,
        rxTargetDataMsgs,
        rxTargetDataBytes,
        rxTargetDataMsgsDiscarded,
        rxTargetDataBytesDiscarded,
        txTargetMsgs,
        txTargetScsiRspMsgs,
        txTargetScsiTaskMgtRspMsgs,
        txTargetLoginRspMsgs,
        txTargetRttMsgs,
        txTargetAsyncEvtMsgs,
        txTargetDataMsgs,
        txTargetDataBytes
     }
    STATUS current
    DESCRIPTION "."

::= { iscsiGroups 3 }

iscsiLunInfoGroup OBJECT-GROUP
    OBJECTS {
        lunId,
     lunSerialNumber,
        rxLunMsgs,
        rxLunScsiCmdMsgs,
        rxLunScsiCmdMsgsRejected,
        rxLunTaskMgtMsgs,
        rxLunTaskMgtMsgsRejected,
        rxLunDataMsgs,
        rxLunDataBytes,
        rxLunDataMsgsDiscarded,
        rxLunDataBytesDiscarded,
        txLunMsgs,
        txLunScsiRspMsgs,
        txLunScsiTaskMgtRspMsgs,
        txLunAsyncEvtMsgs,
        txLunDataMsgs,
        txLunDataBytes,
     lunInquiryString
     }
    STATUS current
    DESCRIPTION "."

::= { iscsiGroups 4 }

iscsiInitiatorInfoGroup OBJECT-GROUP
    OBJECTS {
        initiatorIndex,
        initiatorName,
        status,
        connections,
        rxInitiatorMsgs,
        rxInitiatorPingCmdMsgs,
        rxInitiatorScsiCmdMsgs,
        rxInitiatorScsiCmdMsgsRejected,
        rxInitiatorTaskMgtMsgs,
        rxInitiatorTaskMgtMsgsRejected,
        rxInitiatorLoginCmdMsgs,
        rxInitiatorLoginCmdMsgsRejected,
        rxInitiatorTextCmdMsgs,
        rxInitiatorTextCmdMsgsRejected,
        rxInitiatorInvalidMsgs,
        rxInitiatorDataMsgs,
        rxInitiatorDataBytes,
        rxInitiatorDataMsgsDiscarded,
        rxInitiatorDataBytesDiscarded,
        txInitiatorMsgs,
        txInitiatorPingRspMsgs,
        txInitiatorScsiRspMsgs,
        txInitiatorScsiTaskMgtRspMsgs,
        txInitiatorLoginRspMsgs,
        txInitiatorTextRspMsgs,
        txInitiatorRttMsgs,
        txInitiatorAsyncEvtMsgs,
        txInitiatorInvalidOpcodeMsgs,
        txInitiatorDataMsgs,
        txInitiatorDataBytes
     }
    STATUS current
    DESCRIPTION "."

::= { iscsiGroups 5 }

iscsiConnectionInfoGroup OBJECT-GROUP
    OBJECTS {
        cxnIpAddress,
        cxnTcpPort,
        isid,
        tsid,
        state,
        allowNoRtt,
        initiator,
        authenticator,
        authType,
        msgCheckType,
        dataCheckType,
        rxCxnMsgs,
        rxCxnPingCmdMsgs,
        rxCxnScsiCmdMsgs,
        rxCxnScsiCmdMsgsRejected,
        rxCxnTaskMgtMsgs,
        rxCxnTaskMgtMsgsRejected,
        rxCxnLoginCmdMsgs,
        rxCxnLoginCmdMsgsRejected,
        rxCxnTextCmdMsgs,
        rxCxnTextCmdMsgsRejected,
        rxCxnInvalidMsgs,
        rxCxnDataMsgs,
        rxCxnDataBytes,
        rxCxnDataMsgsDiscarded,
        rxCxnDataBytesDiscarded,
        txCxnMsgs,
        txCxnPingRspMsgs,
        txCxnScsiRspMsgs,
        txCxnScsiTaskMgtRspMsgs,
        txCxnLoginRspMsgs,
        txCxnTextRspMsgs,
        txCxnRttMsgs,
        txCxnAsyncEvtMsgs,
        txCxnInvalidOpcodeMsgs,
        txCxnDataMsgs,
        txCxnDataBytes
        }
    STATUS current
    DESCRIPTION "."

::= { iscsiGroups 6 }

iscsiCompliances OBJECT IDENTIFIER ::= { iscsiConformance 2 }

iscsiCompliance MODULE-COMPLIANCE
     STATUS         current
     DESCRIPTION "."
     MODULE         -- this module
     MANDATORY-GROUPS
          { iscsiGeneralInfoGroup, iscsiPortInfoGroup, iscsiTargetInfoGroup,
          iscsiLunInfoGroup, iscsiInitiatorInfoGroup, iscsiConnectionInfoGroup }
::= { iscsiCompliances 1 }

END
